FME workspace cw9.fmw

Parameters:
- SourceDataset_SHAPEFILE = C:\Users\natal\Desktop\Bazy danych przestrzennych\cwiczenia8-9\bdline_essh_gb\Data\GB\scotland_and_wales_region.shp   # Source Esri Shapefile(s)
- SourceDataset_GEOTIFF = ""C:\Users\natal\Desktop\Bazy danych przestrzennych\cwiczenia8-9\ras250_gb\data\GEOTIFF.tif" "C:\Users\natal\Desktop\Bazy danych przestrzennych\cwiczenia8-9\ras250_gb\data\GEOTIFF_1.tif" "C:\Users\natal\Desktop\Bazy danych przestrzennych\cwiczenia8-9\ras250_gb\data\GEOTIFF_2.tif" "C:\Users\natal\Desktop\Bazy danych przestrzennych\cwiczenia8-9\ras250_gb\data\GEOTIFF_3.tif" "C:\Users\natal\Desktop\Bazy danych przestrzennych\cwiczenia8-9\ras250_gb\data\GEOTIFF_4.tif" "C:\Users\natal\Desktop\Bazy danych przestrzennych\cwiczenia8-9\ras250_gb\data\GEOTIFF_5.tif" "C:\Users\natal\Desktop\Bazy danych przestrzennych\cwiczenia8-9\ras250_gb\data\GEOTIFF_6.tif" "C:\Users\natal\Desktop\Bazy danych przestrzennych\cwiczenia8-9\ras250_gb\data\GEOTIFF_7.tif" "C:\Users\natal\Desktop\Bazy danych przestrzennych\cwiczenia8-9\ras250_gb\data\GEOTIFF_8.tif" "C:\Users\natal\Desktop\Bazy danych przestrzennych\cwiczenia8-9\ras250_gb\data\GEOTIFF_9.tif" "C:\Users\natal\Desktop\Bazy danych przestrzennych\cwiczenia8-9\ras250_gb\data\GEOTIFF_10.tif" "C:\Users\natal\Desktop\Bazy danych przestrzennych\cwiczenia8-9\ras250_gb\data\GEOTIFF_11.tif" "C:\Users\natal\Desktop\Bazy danych przestrzennych\cwiczenia8-9\ras250_gb\data\GEOTIFF_12.tif" "C:\Users\natal\Desktop\Bazy danych przestrzennych\cwiczenia8-9\ras250_gb\data\GEOTIFF_13.tif" "C:\Users\natal\Desktop\Bazy danych przestrzennych\cwiczenia8-9\ras250_gb\data\GEOTIFF_14.tif" "C:\Users\natal\Desktop\Bazy danych przestrzennych\cwiczenia8-9\ras250_gb\data\GEOTIFF_15.tif" "C:\Users\natal\Desktop\Bazy danych przestrzennych\cwiczenia8-9\ras250_gb\data\GEOTIFF_16.tif" "C:\Users\natal\Desktop\Bazy danych przestrzennych\cwiczenia8-9\ras250_gb\data\GEOTIFF_17.tif" "C:\Users\natal\Desktop\Bazy danych przestrzennych\cwiczenia8-9\ras250_gb\data\GEOTIFF_18.tif" "C:\Users\natal\Desktop\Bazy danych przestrzennych\cwiczenia8-9\ras250_gb\data\GEOTIFF_19.tif" "C:\Users\natal\Desktop\Bazy danych przestrzennych\cwiczenia8-9\ras250_gb\data\GEOTIFF_20.tif" "C:\Users\natal\Desktop\Bazy danych przestrzennych\cwiczenia8-9\ras250_gb\data\GEOTIFF_21.tif" "C:\Users\natal\Desktop\Bazy danych przestrzennych\cwiczenia8-9\ras250_gb\data\GEOTIFF_22.tif" "C:\Users\natal\Desktop\Bazy danych przestrzennych\cwiczenia8-9\ras250_gb\data\GEOTIFF_23.tif" "C:\Users\natal\Desktop\Bazy danych przestrzennych\cwiczenia8-9\ras250_gb\data\GEOTIFF_24.tif" "C:\Users\natal\Desktop\Bazy danych przestrzennych\cwiczenia8-9\ras250_gb\data\GEOTIFF_25.tif" "C:\Users\natal\Desktop\Bazy danych przestrzennych\cwiczenia8-9\ras250_gb\data\GEOTIFF_26.tif" "C:\Users\natal\Desktop\Bazy danych przestrzennych\cwiczenia8-9\ras250_gb\data\GEOTIFF_27.tif" "C:\Users\natal\Desktop\Bazy danych przestrzennych\cwiczenia8-9\ras250_gb\data\GEOTIFF_28.tif" "C:\Users\natal\Desktop\Bazy danych przestrzennych\cwiczenia8-9\ras250_gb\data\GEOTIFF_29.tif" "C:\Users\natal\Desktop\Bazy danych przestrzennych\cwiczenia8-9\ras250_gb\data\GEOTIFF_30.tif" "C:\Users\natal\Desktop\Bazy danych przestrzennych\cwiczenia8-9\ras250_gb\data\GEOTIFF_31.tif" "C:\Users\natal\Desktop\Bazy danych przestrzennych\cwiczenia8-9\ras250_gb\data\GEOTIFF_32.tif" "C:\Users\natal\Desktop\Bazy danych przestrzennych\cwiczenia8-9\ras250_gb\data\GEOTIFF_33.tif" "C:\Users\natal\Desktop\Bazy danych przestrzennych\cwiczenia8-9\ras250_gb\data\GEOTIFF_34.tif" "C:\Users\natal\Desktop\Bazy danych przestrzennych\cwiczenia8-9\ras250_gb\data\GEOTIFF_35.tif" "C:\Users\natal\Desktop\Bazy danych przestrzennych\cwiczenia8-9\ras250_gb\data\GEOTIFF_36.tif" "C:\Users\natal\Desktop\Bazy danych przestrzennych\cwiczenia8-9\ras250_gb\data\GEOTIFF_37.tif" "C:\Users\natal\Desktop\Bazy danych przestrzennych\cwiczenia8-9\ras250_gb\data\GEOTIFF_38.tif" "C:\Users\natal\Desktop\Bazy danych przestrzennych\cwiczenia8-9\ras250_gb\data\GEOTIFF_39.tif" "C:\Users\natal\Desktop\Bazy danych przestrzennych\cwiczenia8-9\ras250_gb\data\GEOTIFF_40.tif" "C:\Users\natal\Desktop\Bazy danych przestrzennych\cwiczenia8-9\ras250_gb\data\GEOTIFF_41.tif" "C:\Users\natal\Desktop\Bazy danych przestrzennych\cwiczenia8-9\ras250_gb\data\GEOTIFF_42.tif" "C:\Users\natal\Desktop\Bazy danych przestrzennych\cwiczenia8-9\ras250_gb\data\GEOTIFF_43.tif" "C:\Users\natal\Desktop\Bazy danych przestrzennych\cwiczenia8-9\ras250_gb\data\GEOTIFF_44.tif" "C:\Users\natal\Desktop\Bazy danych przestrzennych\cwiczenia8-9\ras250_gb\data\GEOTIFF_45.tif" "C:\Users\natal\Desktop\Bazy danych przestrzennych\cwiczenia8-9\ras250_gb\data\GEOTIFF_46.tif" "C:\Users\natal\Desktop\Bazy danych przestrzennych\cwiczenia8-9\ras250_gb\data\GEOTIFF_47.tif" "C:\Users\natal\Desktop\Bazy danych przestrzennych\cwiczenia8-9\ras250_gb\data\GEOTIFF_48.tif" "C:\Users\natal\Desktop\Bazy danych przestrzennych\cwiczenia8-9\ras250_gb\data\GEOTIFF_49.tif" "C:\Users\natal\Desktop\Bazy danych przestrzennych\cwiczenia8-9\ras250_gb\data\GEOTIFF_50.tif" "C:\Users\natal\Desktop\Bazy danych przestrzennych\cwiczenia8-9\ras250_gb\data\GEOTIFF_51.tif" "C:\Users\natal\Desktop\Bazy danych przestrzennych\cwiczenia8-9\ras250_gb\data\GEOTIFF_52.tif" "C:\Users\natal\Desktop\Bazy danych przestrzennych\cwiczenia8-9\ras250_gb\data\GEOTIFF_53.tif" "C:\Users\natal\Desktop\Bazy danych przestrzennych\cwiczenia8-9\ras250_gb\data\GEOTIFF_54.tif" "C:\Users\natal\Desktop\Bazy danych przestrzennych\cwiczenia8-9\ras250_gb\data\GEOTIFF_55.tif" "C:\Users\natal\Desktop\Bazy danych przestrzennych\cwiczenia8-9\ras250_gb\data\HP.tif" "C:\Users\natal\Desktop\Bazy danych przestrzennych\cwiczenia8-9\ras250_gb\data\HT.tif" "C:\Users\natal\Desktop\Bazy danych przestrzennych\cwiczenia8-9\ras250_gb\data\HU.tif" "C:\Users\natal\Desktop\Bazy danych przestrzennych\cwiczenia8-9\ras250_gb\data\HW.tif" "C:\Users\natal\Desktop\Bazy danych przestrzennych\cwiczenia8-9\ras250_gb\data\HX.tif" "C:\Users\natal\Desktop\Bazy danych przestrzennych\cwiczenia8-9\ras250_gb\data\HY.tif" "C:\Users\natal\Desktop\Bazy danych przestrzennych\cwiczenia8-9\ras250_gb\data\HZ.tif" "C:\Users\natal\Desktop\Bazy danych przestrzennych\cwiczenia8-9\ras250_gb\data\NA.tif" "C:\Users\natal\Desktop\Bazy danych przestrzennych\cwiczenia8-9\ras250_gb\data\NB.tif" "C:\Users\natal\Desktop\Bazy danych przestrzennych\cwiczenia8-9\ras250_gb\data\NC.tif" "C:\Users\natal\Desktop\Bazy danych przestrzennych\cwiczenia8-9\ras250_gb\data\ND.tif" "C:\Users\natal\Desktop\Bazy danych przestrzennych\cwiczenia8-9\ras250_gb\data\NF.tif" "C:\Users\natal\Desktop\Bazy danych przestrzennych\cwiczenia8-9\ras250_gb\data\NG.tif" "C:\Users\natal\Desktop\Bazy danych przestrzennych\cwiczenia8-9\ras250_gb\data\NH.tif" "C:\Users\natal\Desktop\Bazy danych przestrzennych\cwiczenia8-9\ras250_gb\data\NJ.tif" "C:\Users\natal\Desktop\Bazy danych przestrzennych\cwiczenia8-9\ras250_gb\data\NK.tif" "C:\Users\natal\Desktop\Bazy danych przestrzennych\cwiczenia8-9\ras250_gb\data\NL.tif" "C:\Users\natal\Desktop\Bazy danych przestrzennych\cwiczenia8-9\ras250_gb\data\NM.tif" "C:\Users\natal\Desktop\Bazy danych przestrzennych\cwiczenia8-9\ras250_gb\data\NN.tif" "C:\Users\natal\Desktop\Bazy danych przestrzennych\cwiczenia8-9\ras250_gb\data\NO.tif" "C:\Users\natal\Desktop\Bazy danych przestrzennych\cwiczenia8-9\ras250_gb\data\NR.tif" "C:\Users\natal\Desktop\Bazy danych przestrzennych\cwiczenia8-9\ras250_gb\data\NS.tif" "C:\Users\natal\Desktop\Bazy danych przestrzennych\cwiczenia8-9\ras250_gb\data\NT.tif" "C:\Users\natal\Desktop\Bazy danych przestrzennych\cwiczenia8-9\ras250_gb\data\NU.tif" "C:\Users\natal\Desktop\Bazy danych przestrzennych\cwiczenia8-9\ras250_gb\data\NW.tif" "C:\Users\natal\Desktop\Bazy danych przestrzennych\cwiczenia8-9\ras250_gb\data\NX.tif" "C:\Users\natal\Desktop\Bazy danych przestrzennych\cwiczenia8-9\ras250_gb\data\NY.tif" "C:\Users\natal\Desktop\Bazy danych przestrzennych\cwiczenia8-9\ras250_gb\data\NZ.tif" "C:\Users\natal\Desktop\Bazy danych przestrzennych\cwiczenia8-9\ras250_gb\data\OV.tif" "C:\Users\natal\Desktop\Bazy danych przestrzennych\cwiczenia8-9\ras250_gb\data\SC.tif" "C:\Users\natal\Desktop\Bazy danych przestrzennych\cwiczenia8-9\ras250_gb\data\SD.tif" "C:\Users\natal\Desktop\Bazy danych przestrzennych\cwiczenia8-9\ras250_gb\data\SE.tif" "C:\Users\natal\Desktop\Bazy danych przestrzennych\cwiczenia8-9\ras250_gb\data\SH.tif" "C:\Users\natal\Desktop\Bazy danych przestrzennych\cwiczenia8-9\ras250_gb\data\SJ.tif" "C:\Users\natal\Desktop\Bazy danych przestrzennych\cwiczenia8-9\ras250_gb\data\SK.tif" "C:\Users\natal\Desktop\Bazy danych przestrzennych\cwiczenia8-9\ras250_gb\data\SM.tif" "C:\Users\natal\Desktop\Bazy danych przestrzennych\cwiczenia8-9\ras250_gb\data\SN.tif" "C:\Users\natal\Desktop\Bazy danych przestrzennych\cwiczenia8-9\ras250_gb\data\SO.tif" "C:\Users\natal\Desktop\Bazy danych przestrzennych\cwiczenia8-9\ras250_gb\data\SP.tif" "C:\Users\natal\Desktop\Bazy danych przestrzennych\cwiczenia8-9\ras250_gb\data\SR.tif" "C:\Users\natal\Desktop\Bazy danych przestrzennych\cwiczenia8-9\ras250_gb\data\SS.tif" "C:\Users\natal\Desktop\Bazy danych przestrzennych\cwiczenia8-9\ras250_gb\data\ST.tif" "C:\Users\natal\Desktop\Bazy danych przestrzennych\cwiczenia8-9\ras250_gb\data\SU.tif" "C:\Users\natal\Desktop\Bazy danych przestrzennych\cwiczenia8-9\ras250_gb\data\SV.tif" "C:\Users\natal\Desktop\Bazy danych przestrzennych\cwiczenia8-9\ras250_gb\data\SW.tif" "C:\Users\natal\Desktop\Bazy danych przestrzennych\cwiczenia8-9\ras250_gb\data\SX.tif" "C:\Users\natal\Desktop\Bazy danych przestrzennych\cwiczenia8-9\ras250_gb\data\SY.tif" "C:\Users\natal\Desktop\Bazy danych przestrzennych\cwiczenia8-9\ras250_gb\data\SZ.tif" "C:\Users\natal\Desktop\Bazy danych przestrzennych\cwiczenia8-9\ras250_gb\data\TA.tif" "C:\Users\natal\Desktop\Bazy danych przestrzennych\cwiczenia8-9\ras250_gb\data\TF.tif" "C:\Users\natal\Desktop\Bazy danych przestrzennych\cwiczenia8-9\ras250_gb\data\TG.tif" "C:\Users\natal\Desktop\Bazy danych przestrzennych\cwiczenia8-9\ras250_gb\data\TL.tif" "C:\Users\natal\Desktop\Bazy danych przestrzennych\cwiczenia8-9\ras250_gb\data\TM.tif" "C:\Users\natal\Desktop\Bazy danych przestrzennych\cwiczenia8-9\ras250_gb\data\TQ.tif" "C:\Users\natal\Desktop\Bazy danych przestrzennych\cwiczenia8-9\ras250_gb\data\TR.tif" "C:\Users\natal\Desktop\Bazy danych przestrzennych\cwiczenia8-9\ras250_gb\data\TV.tif""   # Source GeoTIFF File(s) or URL(s)
- DestDataset_POSTGIS = PostGIS_cw9   # Connection

Readers:
- SHAPEFILE_1: SHAPEFILE from $(SourceDataset_SHAPEFILE)
- GEOTIFF_1: GEOTIFF from $(SourceDataset_GEOTIFF)

Writers:
- POSTGIS_1: POSTGIS to $(DestDataset_POSTGIS)

scotland_and_wales_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> Tester
Tester
    BOOL_OP = OR
    TEST_CLAUSE = CASE_INSENSITIVE_TEST @Value(NAME) BEGINS_WITH South Wales
    TEST_MODE = TEST
    PASSED -> Aggregator
Aggregator
    ACCUM_ATTRS_NAME = Drop Incoming Attributes
    AGGREGATE_TYPE = Homogeneous Collection (If Possible)
    MODE = Geometry - Assemble One Level
    SEP = ,
    AGGREGATE -> Clipper [CLIPPER]
GEOTIFF (reader GEOTIFF_1)
    -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterPaletteResolver
RasterPaletteResolver
    -> Exports (writer POSTGIS_1)
Exports (writer POSTGIS_1)
    attributes: _clipped char(3)
